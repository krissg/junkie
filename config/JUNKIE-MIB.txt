-- vim:syntax=mib formatoptions=

JUNKIE-MIB DEFINITIONS ::= BEGIN

IMPORTS
	securactive FROM SECURACTIVE-MIB
	OBJECT-TYPE, MODULE-IDENTITY, Counter64, Gauge32 FROM SNMPv2-SMI
	TruthValue FROM SNMPv2-TC;

junkieMIB MODULE-IDENTITY
	LAST-UPDATED "201011040000Z"
	ORGANIZATION "SecurActive SA"
	CONTACT-INFO "info@securactive.net"
	DESCRIPTION  "Junkie MIB"
	REVISION     "201011040000Z"
	DESCRIPTION  "Initial version"
	::= { securactive 1 }

junkieSystem  OBJECT IDENTIFIER ::= { junkieMIB 1 }
junkieSniffer OBJECT IDENTIFIER ::= { junkieMIB 2 }
junkieParser  OBJECT IDENTIFIER ::= { junkieMIB 3 }

junkieVersion OBJECT-TYPE
	SYNTAX OCTET STRING
	MAX-ACCESS read-only
	STATUS current
	DESCRIPTION "The version of the sniffer currently installed"
	::= { junkieSystem 1 }

sources OBJECT-TYPE
	SYNTAX SEQUENCE OF source
	MAX-ACCESS not-accessible
	STATUS current
	DESCRIPTION
		"This table displays all available statistics per packet source."
	::= { junkieSniffer 1 }

source OBJECT-TYPE
	SYNTAX Source
	MAX-ACCESS not-accessible
	STATUS current
	DESCRIPTION "A source of network packets."
	INDEX { sourceName }
	::= { sources 1 }

Source ::= SEQUENCE {
	sourceName OCTET STRING,
	receivedCount Counter64,
	droppedCount Counter64,
	processedCount Counter64,
	duplicateCount Counter64
}

sourceName OBJECT-TYPE
	SYNTAX OCTET STRING
	MAX-ACCESS read-only
	STATUS current
	DESCRIPTION "the name of the packet source."
	::= { source 1 }

receivedCount OBJECT-TYPE
	SYNTAX Counter64
	MAX-ACCESS read-only
	STATUS current
	DESCRIPTION
		"How many packets were received by the kernel for this source
		 (as reported by libpcap)."
	::= { source 2 }

droppedCount OBJECT-TYPE
	SYNTAX Counter64
	MAX-ACCESS read-only
	STATUS current
	DESCRIPTION
		"How many packets were dropped by the kernel for this source
		 (as reported by libpcap). If you experience a lot of dropped
		 packets you may want to try to increased receive buffer sizes
		 (sysctl net.core.rmem_max)"
	::= { source 3 }

processedCount OBJECT-TYPE
	SYNTAX Counter64
	MAX-ACCESS read-only
	STATUS current
	DESCRIPTION
		"How many packets were handled to the parsing process
		 (this may be less than receivedCount because some received
		 packets may still be waiting in receive buffer)."
	::= { source 4 }

duplicateCount OBJECT-TYPE
	SYNTAX Counter64
	MAX-ACCESS read-only
	STATUS current
	DESCRIPTION
		"Amongst all processed packets, how many were rejected because
		 considered duplicates.
		 If you have a high ratio of duplicates you may want to check your mirroring."
	::= { source 5 }

dupDetectionDelay OBJECT-TYPE
	SYNTAX Integer32
	UNITS "microseconds"
	MAX-ACCESS read-write
	STATUS current
	DESCRIPTION
		"Number of seconds between two packets that can't be duplicates."
	::= { junkieSniffer 2 }

-- Stats table for parsers

parsers OBJECT-TYPE
	SYNTAX SEQUENCE OF parser
	MAX-ACCESS not-accessible
	STATUS current
	DESCRIPTION
		"This table displays all available statistics per protocolar parser."
	::= { junkieParser 1 }

parser OBJECT-TYPE
	SYNTAX Parser
	MAX-ACCESS not-accessible
	STATUS current
	DESCRIPTION "A row describing a parser."
	INDEX { protoName }
	::= { parsers 1 }

Parser ::= SEQUENCE {
	protoName OCTET STRING,
	frameCount Counter64,
	byteCount Counter64,
	nbInstances Gauge32
}

protoName OBJECT-TYPE
	SYNTAX OCTET STRING
	MAX-ACCESS read-only
	STATUS current
	DESCRIPTION "The name of the parsed protocol."
	::= { parser 1 }

frameCount OBJECT-TYPE
	SYNTAX Counter64
	MAX-ACCESS read-only
	STATUS current
	DESCRIPTION
		"How many frames (or, in some rare occasions, frame fragments) 
		 were handled by this parser."
	::= { parser 2 }

byteCount OBJECT-TYPE
	SYNTAX Counter64
	UNITS "bytes"
	MAX-ACCESS read-only
	STATUS current
	DESCRIPTION
		"How many bytes were handled by this parser."
	::= { parser 3 }

nbInstances OBJECT-TYPE
	SYNTAX Gauge32
	MAX-ACCESS read-only
	STATUS current
	DESCRIPTION
		"How many instances of this parser are currently running simultaneously."
	::= { parser 4 }

-- More specific stats for parsers that are also multiplexers

muxers OBJECT-TYPE
	SYNTAX SEQUENCE OF muxer
	MAX-ACCESS not-accessible
	STATUS current
	DESCRIPTION
		"This table completes the parsers table with additional statistics for
		 parsers that multiplex their payload amongst several possible subparsers
		 (for instance an IP parser multiplex its payload according to source address,
		 dest address and protocol, while a TCP parser multiplex its payload according
		 to the source and dest ports)."
	::= { junkieParser 2 }

muxer OBJECT-TYPE
	SYNTAX Muxer
	MAX-ACCESS not-accessible
	STATUS current
	DESCRIPTION "A row giving statistics on a given multiplexer."
	INDEX { muxName }
	::= { muxers 1 }

Muxer ::= SEQUENCE {
	muxerName OCTET STRING,
	muxerHashSize Gauge32,
	muxerMaxChildren Gauge32,
	muxerInfanticide Counter32,
	muxerCollisions Counter64,
	muxerLookups Counter64
}

muxerName OBJECT-TYPE
	SYNTAX OCTET STRING
	MAX-ACCESS read-only
	STATUS current
	DESCRIPTION "The name of the multiplexed protocol."
	::= { muxer 1 }

muxerHashSize OBJECT-TYPE
	SYNTAX Gauge32
	MAX-ACCESS read-only
	STATUS current
	DESCRIPTION "The current hash size (in entries) for each instance of this multiplexer."
	::= { muxer 2 }

muxerMaxChildren OBJECT-TYPE
	SYNTAX Gauge32
	MAX-ACCESS read-only
	STATUS current
	DESCRIPTION
		"The max number of children allowed for each instance of this multiplexer
		 (0 for no limit)."
	::= { muxer 3 }

muxerInfanticide OBJECT-TYPE
	SYNTAX Counter32
	MAX-ACCESS read-only
	STATUS current
	DESCRIPTION
		"How many children of this multiplexer were killed due to the max number of
		 child limitation."
	::= { muxer 4 }

muxerCollisions OBJECT-TYPE
	SYNTAX Counter64
	MAX-ACCESS read-only
	STATUS current
	DESCRIPTION "Number of collisions while performing children lookups."
	::= { muxer 5 }

muxerLookups OBJECT-TYPE
	SYNTAX Counter64
    MAX-ACCESS read-only
    STATUS current
    DESCRIPTION
		"Number of lookups for children of this multiplexer.
		 The ratio between number of collisions and number of lookups
		 gives a good idea of the performance of this hash and weither it is
		 sized correctly."
	::= { muxer 6 }

END
